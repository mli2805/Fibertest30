VEEX-IGMALARM-MIB DEFINITIONS ::= BEGIN

IMPORTS	enterprises
		FROM RFC1155-SMI
	OBJECT-TYPE
		FROM RFC1212
	TRAP-TYPE
		FROM RFC-1215;

--
-- Node definitions
--

-- 1.3.6.1.4.1.36290
veex OBJECT IDENTIFIER ::= { enterprises 36290 }

-- 1.3.6.1.4.1.36290.1
status OBJECT-TYPE
	SYNTAX OCTET STRING
	ACCESS read-only
	STATUS mandatory
	::= { veex 1 }

-- 1.3.6.1.4.1.36290.2
alarmType OBJECT-TYPE
	SYNTAX OCTET STRING
	ACCESS read-only
	STATUS mandatory
	::= { veex 2 }

-- 1.3.6.1.4.1.36290.3
alarmLevel OBJECT-TYPE
	SYNTAX OCTET STRING
	ACCESS read-only
	STATUS mandatory
	::= { veex 3 }

-- 1.3.6.1.4.1.36290.4
timestamp OBJECT-TYPE
	SYNTAX OCTET STRING
	ACCESS read-only
	STATUS mandatory
	::= { veex 4 }

-- 1.3.6.1.4.1.36290.5
deviceSerial OBJECT-TYPE
	SYNTAX OCTET STRING
	ACCESS read-only
	STATUS mandatory
	::= { veex 5 }

-- 1.3.6.1.4.1.36290.6
deviceIp OBJECT-TYPE
	SYNTAX OCTET STRING
	ACCESS read-only
	STATUS mandatory
	::= { veex 6 }

-- 1.3.6.1.4.1.36290.7
port OBJECT-TYPE
	SYNTAX OCTET STRING
	ACCESS read-only
	STATUS mandatory
	::= { veex 7 }

-- 1.3.6.1.4.1.36290.8
distance OBJECT-TYPE
	SYNTAX OCTET STRING
	ACCESS read-only
	STATUS mandatory
	::= { veex 8 }
	
-- 1.3.6.1.4.1.36290.10
specificTrapValue OBJECT-TYPE
	SYNTAX INTEGER
	ACCESS read-only
	STATUS mandatory
	::= { veex 10 }	

-- 1.3.6.1.4.1.36290.90
testMessage OBJECT-TYPE
	SYNTAX OCTET STRING
	ACCESS read-only
	STATUS mandatory
	::= { veex 90 }
	
--
-- Trap definitions, Return
--


testTrap TRAP-TYPE
	ENTERPRISE veex
	VARIABLES { testMessage }
	::= 600

opticalEvent TRAP-TYPE
	ENTERPRISE veex
	VARIABLES { status, alarmType, alarmLevel, timestamp, deviceSerial, deviceIp, port,  distance }
	::= 610


END
